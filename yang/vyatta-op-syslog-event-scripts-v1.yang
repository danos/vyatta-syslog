module vyatta-op-syslog-event-scripts-v1 {
	namespace "urn:vyatta.com:mgmt:vyatta-op-syslog-event-scripts:1";
	prefix vyatta-op-syslog-event-scripts-v1;

	import vyatta-opd-extensions-v1 {
		prefix opd;
	}
	import vyatta-op-add-v1 {
		prefix add;
	}
	import vyatta-op-delete-v1 {
		prefix delete;
	}
	import vyatta-op-delete-syslog-file-v1 {
		prefix syslog-delete;
	}

	organization "AT&T Inc.";
	contact
		"AT&T
		 Postal: 208 S. Akard Street
		         Dallas, TX 75202
		 Web: www.att.com";

	description
		"Copyright (c) 2021, AT&T Intellectual Property.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		Defines the 'syslog' level under 'delete' for  operational CLI";

	revision 2021-10-25 {
		description "Initial version";
	}

	opd:augment /add:add {
		opd:command syslog {
			opd:help "Add syslog content";

			opd:option event-script {
				opd:help "Add a syslog event script";
				type string {
					opd:help "File name of script to add";
					pattern '[a-zA-Z0-9._\-/]+' {
						error-message "Must be alphanumeric, underscore, hyphen, dot or slash";
					}
				}
				opd:on-enter 'vyatta_syslog_event_scripts -action add -location "$4"';

				opd:option to {
					opd:help "Name to assign to event-script";
					type string {
						pattern '[a-zA-Z0-9._\-]+' {
							error-message "Must be alphanumeric, underscore, hyphen or dot";
						}
					}
					opd:on-enter 'vyatta_syslog_event_scripts -action add -location "$4" -script_name "$6" ';

				}
			}
		}
	}

	opd:augment /delete:delete/syslog-delete:syslog {
		opd:option event-script {
			opd:help "Delete syslog event script";
			type string {
				opd:help "Name of event script";
			}
			opd:allowed 'vyatta_syslog_event_scripts -action listscripts';
			opd:on-enter 'vyatta_syslog_event_scripts -action delete -script_name "$4"';
		}
	}
}

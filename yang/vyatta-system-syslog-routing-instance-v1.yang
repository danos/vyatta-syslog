module vyatta-system-syslog-routing-instance-v1 {
	namespace "urn:vyatta.com:mgmt:vyatta-system-syslog-routing-instance:1";
	prefix vyatta-system-syslog-routing-instance-v1;

	import vyatta-system-syslog-v1 {
		prefix syslog;
	}
	import vyatta-routing-v1 {
		prefix routing;
	}
	import vyatta-routing-instance-interfaces-v1 {
		prefix rif;
	}

	organization "AT&T Inc.";
	contact
		"AT&T
		 Postal: 208 S. Akard Street
		         Dallas, TX 75202
		 Web: www.att.com";

	description
		"Copyright (c) 2018-2019 AT&T Intellectual Property
		 All rights reserved.

		 Copyright (c) 2016 by Brocade Communications Systems, Inc.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 Syslog VRF configuration";

	revision 2019-12-11 {
		description "Restrict source-interface to UDP";
	}
	revision 2018-04-23 {
		description "Add routing instance constraint for source-interface leaf";
	}

	revision 2016-04-22 {
		description "Initial revision";
	}

	augment /routing:routing/routing:routing-instance/routing:system {
		uses syslog:syslog-base;
	}

	augment /routing:routing/routing:routing-instance/routing:system/syslog {
		uses syslog:syslog-remote {
			refine source-interface {
				must "current() = /routing:routing/routing:routing-instance" +
					"[routing:instance-name = current()/../../../routing:instance-name]" +
					"/rif:interface/rif:name" {
					error-message "Interface must be configured in this routing instance";
				}
				must "not(../host/protocol) or (../host/protocol = 'udp')" {
					error-message "Source-interface is only supported over UDP.";
				}
			}
		}
	}

}

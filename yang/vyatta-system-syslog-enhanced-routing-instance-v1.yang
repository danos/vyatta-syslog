module vyatta-system-syslog-enhanced-routing-instance-v1 {
	namespace "urn:vyatta.com:mgmt:vyatta-system-syslog-enhanced-routing-instance:1";
	prefix vyatta-system-syslog-enhanced-routing-instance-v1;

	import vyatta-routing-instance-interfaces-v1 {
		prefix rif;
	}

	import vyatta-routing-v1 {
		prefix routing;
	}

	import vyatta-system-v1 {
		prefix system;
	}

	import vyatta-system-syslog-enhanced-v1 {
		prefix sle;
	}

	organization "AT&T Inc.";
	contact
		"AT&T
		 Postal: 208 S. Akard Street
		         Dallas, TX 75202
		 Web: www.att.com";

	description
		"Copyright (c) 2020 AT&T Intellectual Property
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 VRF support for Enhanced Syslog.";

	revision 2020-12-03 {
		description "Initial revision.";
	}

	augment /system:system/sle:syslog-enhanced/sle:host {
		uses routing:routing-instance-leaf {
			refine routing-instance {
				must "not(../sle:source-interface) or " +
						"/routing:routing" +
						"/routing:routing-instance[routing:instance-name = current()]" +
						"/rif:interface[rif:name = current()/../sle:source-interface]" {
					error-message "Source interface does not match routing instance";
				}
			}
		}
	}
}
